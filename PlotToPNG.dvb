Attribute VB_Name = "DWGToPNG"
''' **************
''' *** HEADER ***
''' **************

' Module: Export DWG to PNG

' Author: Mike Halbheer, Terradata Opfikon


''' ************************
''' *** DEFINE VARIABLES ***
''' ************************

' Coordinates of the corner points
Dim N_BottomLeft As Long
Dim E_BottomLeft As Long
Dim N_TopRight As Long
Dim E_TopRight As Long

' Size of the area included
Dim Area_Height As Long
Dim Area_Width As Long
Dim Area As Double

' Viewpoert Dimensions
Dim Viewport_Center(0 To 2) As Double
Dim Viewport_Width As Double
Dim Viewport_Height As Double

' Temporary Layout for plotting
Dim PNG_Export_Layout As AcadLayout
Dim PS_Viewport As AcadPViewport

' Resolution of the image
Dim Resolution As Single

' Array to hold available paper sizes
' Needs to be ordered by size!
Dim paper_format_names(0 To 3) As String
Dim paper_formats(0 To 3) As Long

' Name of the plotter being used
' Plotters need to have the formats listed under paper_format_names available
Dim plotter_names(0 To 1) As String

' Name of the temporary layout
Const Layout_Name = "TEDAMOS"



''' **************************
''' *** DEFINE SUBROUTINES ***
''' **************************

Public Sub DWG_To_PNG()

    ''' DEFINE AVAILABLE PLOTTERS
    
    plotter_names(0) = "DWG to PNG (Grauwerte).pc3"
    plotter_names(1) = "DWG to PNG (Farbe).pc3"

    ''' DEFINE AVAILABLE PAPER FORMATS

    paper_format_names(0) = "UserDefinedRaster (7500.00 x 7500.00Pixel)"
    paper_format_names(1) = "UserDefinedRaster (10000.00 x 10000.00Pixel)"
    paper_format_names(2) = "UserDefinedRaster (25000.00 x 25000.00Pixel)"
    paper_format_names(3) = "UserDefinedRaster (35000.00 x 35000.00Pixel)"
    
    paper_formats(0) = 7500
    paper_formats(1) = 10000
    paper_formats(2) = 25000
    paper_formats(3) = 35000
    
    ''' Pick extent to be exported
    
    On Error GoTo Pick_Error
        Point_BottomLeft = ThisDrawing.Utility.GetPoint(, "Untere linke Ecke auswählen.")
        Point_TopRight = ThisDrawing.Utility.GetPoint(, "Obere rechte Ecke auswählen.")
    GoTo Pick_Success
    
' User interupts picking procedure. End execution
Pick_Error:
    End
    
' Picking was successful
Pick_Success:

    Dim Color_Scale As Integer
    ' Pick color scal
    With Farbauswahl
        .show ' Show the Form
        Color_Scale = .Color_Scale ' Read the Value
    End With

    ' Get coodinates out of point objects
    N_BottomLeft = Point_BottomLeft(1)
    E_BottomLeft = Point_BottomLeft(0)
    
    N_TopRight = Point_TopRight(1)
    E_TopRight = Point_TopRight(0)
    
    ' Calculates area size
    Area_Height = (N_TopRight - N_BottomLeft)
    Area_Width = (E_TopRight - E_BottomLeft)
    
    Area = Area_Width * Area_Height
    
    ' Define Resolution based on the area size
    ' to keep file sizes small
    If Area <= 10000 Then
        Resolution = 100
    ElseIf Area <= 22500 Then
        Resolution = 50
    Else
        Resolution = 20
    End If
    
    ' Define viewport size
    Viewport_Width = Area_Width * Resolution
    Viewport_Height = Area_Height * Resolution
    
    ''' Find the best fitting paper size
    Dim Paper_Format
    
    ' If the image fits, choose the size
    For i = LBound(paper_formats) To (UBound(paper_formats) - LBound(paper_formats))
        If Viewport_Width <= paper_formats(i) And Viewport_Height <= paper_formats(i) Then
            Paper_Format = paper_format_names(i)
            Exit For
        End If
    Next i
    
    ' Tell user if no paper format fits
    If IsEmpty(Paper_Format) Then
        MsgBox "Kein passendes Papier Format verfügbar. Bitte wende dich an Marianne Deuber."
        End
    End If
    
    ' If for any reason the temporary layout still exists, delete it
    For Each Layout In ThisDrawing.Layouts
        If 0 = StrComp(Layout.Name, Layout_Name, vbTextCompare) Then ThisDrawing.Layouts.Item(Layout_Name).Delete
    Next Layout
    
    ' Create the layout
    Set PNG_Export_Layout = ThisDrawing.Layouts.Add(Layout_Name)
    ThisDrawing.ActiveLayout = PNG_Export_Layout
    
    ' Define the plotter and paper size
    ThisDrawing.ActiveLayout.ConfigName = plotter_names(Color_Scale)
    ThisDrawing.ActiveLayout.CanonicalMediaName = Paper_Format ' Paper formats are dependent on the used plotter
    
    ' Delete the default viewport
    For Each Item In ThisDrawing.PaperSpace
        If TypeName(Item) = "IAcadPViewport" Then
            Item.Delete
        End If
    Next
    
    ' Define the viewport center based on the corner dimensions
    Viewport_Center(0) = Viewport_Width / 2
    Viewport_Center(1) = Viewport_Height / 2
    Viewport_Center(2) = 0

    ' Create the viewport
    Set PS_Viewport = ThisDrawing.PaperSpace.AddPViewport(Viewport_Center, Viewport_Width, Viewport_Height)
    
    ' Display the viewport for easier use
    PS_Viewport.Display (True)
    PS_Viewport.ViewportOn = True
    
    ' Define the scale of the viewport, so the image always fills it
    PS_Viewport.StandardScale = acVp1_1
    
    ' Change to model space to manipulate the viewport
    ThisDrawing.MSpace = True
    
    ' Set the viewport to active for easier work
    ThisDrawing.ActivePViewport = PS_Viewport
    
    ' Zoom the model to the viewport size
    ZoomWindow Point_BottomLeft, Point_TopRight
    
    ' Regenerate the viewport
    ThisDrawing.Regen (acAllViewports)
    
    ' Set the plotter to portrait mode
    ThisDrawing.ActiveLayout.PlotRotation = ac0degrees
    
    ' Plot the resulting image
    ThisDrawing.Plot.PlotToDevice plotter_name
    
    ' Get the path of the currently active document
    docpath = ActiveDocument.Path
    docname_raw = ActiveDocument.Name
    docname = CreateObject("Scripting.FileSystemObject").GetBaseName(docname_raw)
    
    docpath_full = docpath & "\" & docname
    
    ' Define a new txt file to write the coordinates to
    Dim FSO As Object
    Set FSO = CreateObject("Scripting.FileSystemObject")
    txt_path = docpath_full & "-TEDAMOS_Coords.txt"
    Set Out_File = FSO.CreateTextFile(txt_path)
    Out_File.WriteLine "P E N"
    Out_File.WriteLine "NW " & CStr(E_BottomLeft) & " " & CStr(N_TopRight)
    Out_File.WriteLine "SE " & CStr(E_TopRight) & " " & CStr(N_BottomLeft)
    ' Note: The following line will be deleted in the Python script and is only
    ' used for reference of the resolution in the Python script
    Out_File.WriteLine "_ " & CStr(Resolution) & " 0"
    Out_File.Close
    
    ' Remove the pointer so memory cleanup can occur
    Set File_Sys_Obj = Nothing
    Set Out_File = Nothing
    
    ' Define the path o
    Dim exepath As String
    exepath = "P:\AutoCAD_PlotToPNG\dist\crop_plot.exe"
    
    ' Build the shell command to be sent
    ShellCommand = """" & exepath & """" & " " & """" & docpath_full & "-" & Layout_Name & ".png" & """" & " " & """" & txt_path & """"
    
    ' Send the shell command to a command shell
    ShellProcess.ExecCmd CStr(ShellCommand)
    
    ' Delete the temporary layout
    ThisDrawing.Layouts.Item(Layout_Name).Delete
    
    ' Tell User about end
    MsgBox "Abgeschlossen."
    
End Sub

Attribute VB_Name = "Farbauswahl"
Attribute VB_Base = "0{74BF2816-FF7F-4406-B7E3-6DBFB2E40AE2}{6618889F-C879-48AB-9372-F06F3E1D8360}"
Attribute VB_GlobalNameSpace = False
Attribute VB_Creatable = False
Attribute VB_PredeclaredId = True
Attribute VB_Exposed = False
Attribute VB_TemplateDerived = False
Attribute VB_Customizable = False
Public Color_Scale As Integer

Private Sub Farbe_Click()
    Color_Scale = 1
    Farbauswahl.Hide
End Sub

Private Sub Grau_Click()
    Color_Scale = 0
    Farbauswahl.Hide
End Sub

Attribute VB_Name = "ShellProcess"
Option Explicit

Private Type STARTUPINFO
cb As Long
lpReserved As String
lpDesktop As String
lpTitle As String
dwX As Long
dwY As Long
dwXSize As Long
dwYSize As Long
dwXCountChars As Long
dwYCountChars As Long
''' CREDIT: Microsoft Visual Basic Documentation

dwFillAttribute As Long
dwFlags As Long
wShowWindow As Integer
cbReserved2 As Integer
lpReserved2 As Long
hStdInput As Long
hStdOutput As Long
hStdError As Long
End Type

Private Type PROCESS_INFORMATION
hProcess As Long
hThread As Long
dwProcessID As Long
dwThreadID As Long
End Type

Private Declare PtrSafe Function WaitForSingleObject Lib "kernel32" (ByVal hHandle As Long, ByVal dwMilliseconds As Long) As Long

Private Declare PtrSafe Function CreateProcessA Lib "kernel32" (ByVal lpApplicationName As Long, ByVal lpCommandLine As String, ByVal lpProcessAttributes As Long, ByVal lpThreadAttributes As Long, ByVal bInheritHandles As Long, ByVal dwCreationFlags As Long, ByVal lpEnvironment As Long, ByVal lpCurrentDirectory As Long, lpStartupInfo As STARTUPINFO, lpProcessInformation As PROCESS_INFORMATION) As Long

Private Declare PtrSafe Function CloseHandle Lib "kernel32" (ByVal hObject As Long) As Long

Private Const NORMAL_PRIORITY_CLASS = &H20&
Private Const INFINITE = -1&

Public Sub ExecCmd(cmdline As String)
    Dim proc As PROCESS_INFORMATION
    Dim start As STARTUPINFO
    Dim ReturnValue As Integer
    
    ' Initialize the STARTUPINFO structure:
    start.cb = Len(start)
    
    ' Start the shelled application:
    ReturnValue = CreateProcessA(0&, cmdline$, 0&, 0&, 1&, _
    NORMAL_PRIORITY_CLASS, 0&, 0&, start, proc)
    
    ' Wait for the shelled application to finish:
    Do
    ReturnValue = WaitForSingleObject(proc.hProcess, 0)
    DoEvents
    Loop Until ReturnValue <> 258
    
    ReturnValue = CloseHandle(proc.hProcess)
End Sub

Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True

Private Sub AcadDocument_BeginSave(ByVal FileName As String)

End Sub
